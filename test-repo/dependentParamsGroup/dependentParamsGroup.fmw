FME workspace dependentParamsGroup.fmw

Parameters:
- PARAMETER = two   # dropdown 1
- PARAMETER_2 =   # dropdown 2
- PARAMETER_3 = test value   # Enter Text Data
- PARAMETER_5 = 1,0.615686,0.960784   # Enter a Color
- PARAMETER_4 = <Unused>   # Parameter Group
- PARAMETER_6 = Group Data   # Enter Group Data
- PARAMETER_7 =   # A message for the user
- PARAMETER_8 = 10   # Enter Numeric Data

Creator
    GEOMTYPE = Geometry Object
    NUM = 1
    CREATED -> Logger
Logger
    LOG_FEATURE = LOG_ONLY
    MAXCOORDS = 20
    MAXFEATS = 20
    MESSAGE = Feature is:
    SEVERITY = INFO
