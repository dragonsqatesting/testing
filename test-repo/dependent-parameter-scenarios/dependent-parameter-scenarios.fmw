FME workspace dependent-parameter-scenarios.fmw

Parameters:
- PARAMETER =   # "Pine Tree"%"Rose Bush" Select a Plant
- PARAMETER_8 =   # Favourite Pine Tree
- PARAMETER_9 =   # Favourite Rose Bush
- PARAMETER_11 =   # Location
- PARAMETER_10 =   # Colour
- PARAMETER_2 = <Unused>   # Pine Tree Facts
- PARAMETER_3 =   # A pine is any conifer tree or shrub in the genus Pinus of the family Pinaceae.
- PARAMETER_4 = 0.309804,0.560784,0   # Enter a Color
- PARAMETER_5 = <Unused>   # Rose Bush Facts
- PARAMETER_7 =   # A rose is either a woody perennial flowering plant of the genus Rosa, in the family Rosaceae, or the flower it bears.
- PARAMETER_6 =   # Enter Text Data
- PARAMETER_12 = <Unused>   # Submit Information
- PARAMETER_14 =   # Enter Data
- PARAMETER_13 =   # "" Upload Image
- PARAMETER_16 =   # Image Location
- PARAMETER_15 = <Unused>   # Location Attributes
- PARAMETER_17 =   # GEOM_TYPE:POLYGON,BOX,LINE,POINT Select Geometry
- PARAMETER_19 = <Unused>   # Hidden if Pine Tree
- PARAMETER_18 =   # Enter a Date
- PARAMETER_20 = <Unused>   # PARAMETER_21 Shown if No Plant Selected
- PARAMETER_21 =   # FAMILY:PostgreSQL Select a Database Connection

Creator
    GEOMTYPE = Geometry Object
    NUM = 1
    CREATED -> Logger
Logger
    LOG_FEATURE = LOG_ONLY
    MAXCOORDS = 20
    MAXFEATS = 20
    MESSAGE = Feature is:
    SEVERITY = INFO
