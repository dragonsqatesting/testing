FME workspace groupBox-checkstate.fmw

Parameters:
- PARAMETER = <Unused>   # Parameter Group
- PARAMETER_2 =   # Enter a Color
- PARAMETER_3 = <Unused>   # PARAMETER_4 Parameter Group 2
- PARAMETER_4 =   # Enter Numeric Data
- PARAMETER_5 =   # Enter Text Data

Creator
    GEOMTYPE = Geometry Object
    NUM = 1
    CREATED -> Logger
Logger
    LOG_FEATURE = LOG_ONLY
    MAXCOORDS = 20
    MAXFEATS = 20
    MESSAGE = Feature is:
    SEVERITY = INFO
