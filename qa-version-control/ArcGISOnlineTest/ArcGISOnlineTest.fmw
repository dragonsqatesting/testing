FME workspace ArcGISOnlineTest.fmw

Readers:
- ARCGISONLINEFEATURES_1: ARCGISONLINEFEATURES

CellSignals (reader ARCGISONLINEFEATURES_1)
    attributes: ID Integer, StationID Integer, Power Double, Quality Single, num_measures SmallInteger, Code String(50), recorded_tstamp Date, longitude Double, latitude Double, updateCode String(20), globalid GlobalID(38), OBJECTID OID
    -> Logger
Logger
    LOG_FEATURE = LOG_ONLY
    MAXCOORDS = 20
    MAXFEATS = 20
    MESSAGE = Feature is:
    SEVERITY = INFO
