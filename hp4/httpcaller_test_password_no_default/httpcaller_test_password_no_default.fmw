FME workspace httpcaller_test_password_no_default.fmw

Parameters:
- TARGET_URL = http://clownfish.base.safe.com/fmeapiv4/repositories   # Request URL
- AUTH_USERNAME = admin   # HTTP Authentication Username
- AUTH_PASSWORD =   # HTTP Authentication Password

Creator
    GEOMTYPE = Geometry Object
    NUM = 1
    CREATED -> HTTPCaller
HTTPCaller
    AUTH_METHOD_TYPE = BASIC
    AUTH_PASSWORD = $(AUTH_PASSWORD)
    AUTH_USERNAME = $(AUTH_USERNAME)
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = $(TARGET_URL)
    TRANSFER_TIMEOUT_LENGTH = 90
    USE_COOKIES = No
    VERIFY_SSL_CERTIFICATES = Yes
    AUTH_METHOD = Basic
    -> Logger
    <REJECTED> -> Inspector
Logger
    LOG_FEATURE = LOG_ONLY
    MAXCOORDS = 20
    MAXFEATS = 20
    MESSAGE = Feature is: @Value(_http_status_code) , @Value(_response_body)
    SEVERITY = INFO
Inspector
