FME workspace publishTest2.fmw

Parameters:
- UPLOAD_FILE = $(FME_SHAREDRESOURCE_DATA)/binu/test2.fmw   # Upload File

Creator
    GEOMTYPE = Geometry Object
    NUM = 1
    CREATED -> HTTPCaller
HTTPCaller
    VERIFY_SSL_CERTIFICATES = Yes
    TARGET_URL = http://sqshw64-18109/fmerest/v3/repositories/binu/items/test.fmw
    AUTH_METHOD = Basic
    TRANSFER_TIMEOUT_LENGTH = 90
    FOLLOW_REDIRECTS = Yes
    STATUS_CODE_ATTR = _http_status_code
    CONNECTION_TIMEOUT_LENGTH = 60
    UPLOAD_FILE = $(UPLOAD_FILE)
    TARGET_ATTR = _response_body
    SAVE_FILE = Attribute
    AUTH_USERNAME = admin
    UPLOAD_TYPE = Upload From File
    HTTP_METHOD = PUT
    UPLOAD_CONTENT_TYPE = Binary (application/octet-stream)
    USE_COOKIES = No
    TARGET_ATTR_ENCODING = auto-detect
    ERROR_ATTR = _error
    RESPONSE_HEADER_LIST_ATTR = _headers
    CUSTOM_HEADERS = Content-Type;application/octet-stream
    AUTH_PASSWORD =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
    -> Logger
Logger
    MESSAGE = Feature is:
    MAXCOORDS = 20
    MAXFEATS = 20
